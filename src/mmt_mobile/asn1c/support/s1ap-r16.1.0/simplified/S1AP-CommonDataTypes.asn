-- Derived from 36413-g10.asn by src/mmt_mobile/asn1c/s1ap-simplify.py (issue #523).
-- Do not edit: `make -C src/mmt_mobile/asn1c gen-s1ap` rewrites it.

S1AP-CommonDataTypes { itu-t (0) identified-organization (4) etsi (0) mobileDomain (0) eps-Access (21) modules (3) s1ap (1) version1 (1) s1ap-CommonDataTypes (3) }

DEFINITIONS AUTOMATIC TAGS ::=

BEGIN

S1ap-Criticality ::= ENUMERATED { reject, ignore, notify }

S1ap-Presence ::= ENUMERATED { optional, conditional, mandatory }

S1ap-PrivateIE-ID ::= CHOICE {
	local				INTEGER (0..65535),
	global				OBJECT IDENTIFIER
}

S1ap-ProcedureCode ::= INTEGER {
	id-HandoverPreparation(0),
	id-HandoverResourceAllocation(1),
	id-HandoverNotification(2),
	id-PathSwitchRequest(3),
	id-HandoverCancel(4),
	id-E-RABSetup(5),
	id-E-RABModify(6),
	id-E-RABRelease(7),
	id-E-RABReleaseIndication(8),
	id-InitialContextSetup(9),
	id-Paging(10),
	id-downlinkNASTransport(11),
	id-initialUEMessage(12),
	id-uplinkNASTransport(13),
	id-Reset(14),
	id-ErrorIndication(15),
	id-NASNonDeliveryIndication(16),
	id-S1Setup(17),
	id-UEContextReleaseRequest(18),
	id-DownlinkS1cdma2000tunnelling(19),
	id-UplinkS1cdma2000tunnelling(20),
	id-UEContextModification(21),
	id-UECapabilityInfoIndication(22),
	id-UEContextRelease(23),
	id-eNBStatusTransfer(24),
	id-MMEStatusTransfer(25),
	id-DeactivateTrace(26),
	id-TraceStart(27),
	id-TraceFailureIndication(28),
	id-ENBConfigurationUpdate(29),
	id-MMEConfigurationUpdate(30),
	id-LocationReportingControl(31),
	id-LocationReportingFailureIndication(32),
	id-LocationReport(33),
	id-OverloadStart(34),
	id-OverloadStop(35),
	id-WriteReplaceWarning(36),
	id-eNBDirectInformationTransfer(37),
	id-MMEDirectInformationTransfer(38),
	id-PrivateMessage(39),
	id-eNBConfigurationTransfer(40),
	id-MMEConfigurationTransfer(41),
	id-CellTrafficTrace(42),
	id-Kill(43),
	id-downlinkUEAssociatedLPPaTransport(44),
	id-uplinkUEAssociatedLPPaTransport(45),
	id-downlinkNonUEAssociatedLPPaTransport(46),
	id-uplinkNonUEAssociatedLPPaTransport(47),
	id-UERadioCapabilityMatch(48),
	id-PWSRestartIndication(49),
	id-E-RABModificationIndication(50),
	id-PWSFailureIndication(51),
	id-RerouteNASRequest(52),
	id-UEContextModificationIndication(53),
	id-ConnectionEstablishmentIndication(54),
	id-UEContextSuspend(55),
	id-UEContextResume(56),
	id-NASDeliveryIndication(57),
	id-RetrieveUEInformation(58),
	id-UEInformationTransfer(59),
	id-eNBCPRelocationIndication(60),
	id-MMECPRelocationIndication(61),
	id-SecondaryRATDataUsageReport(62)
} (0..255)

S1ap-ProtocolExtensionID ::= INTEGER (0..65535)

S1ap-ProtocolIE-ID ::= INTEGER {
	id-MME-UE-S1AP-ID(0),
	id-HandoverType(1),
	id-Cause(2),
	id-SourceID(3),
	id-TargetID(4),
	id-eNB-UE-S1AP-ID(8),
	id-E-RABSubjecttoDataForwardingList(12),
	id-E-RABtoReleaseListHOCmd(13),
	id-E-RABDataForwardingItem(14),
	id-E-RABReleaseItemBearerRelComp(15),
	id-E-RABToBeSetupListBearerSUReq(16),
	id-E-RABToBeSetupItemBearerSUReq(17),
	id-E-RABAdmittedList(18),
	id-E-RABFailedToSetupListHOReqAck(19),
	id-E-RABAdmittedItem(20),
	id-E-RABFailedtoSetupItemHOReqAck(21),
	id-E-RABToBeSwitchedDLList(22),
	id-E-RABToBeSwitchedDLItem(23),
	id-E-RABToBeSetupListCtxtSUReq(24),
	id-TraceActivation(25),
	id-NAS-PDU(26),
	id-E-RABToBeSetupItemHOReq(27),
	id-E-RABSetupListBearerSURes(28),
	id-E-RABFailedToSetupListBearerSURes(29),
	id-E-RABToBeModifiedListBearerModReq(30),
	id-E-RABModifyListBearerModRes(31),
	id-E-RABFailedToModifyList(32),
	id-E-RABToBeReleasedList(33),
	id-E-RABFailedToReleaseList(34),
	id-E-RABItem(35),
	id-E-RABToBeModifiedItemBearerModReq(36),
	id-E-RABModifyItemBearerModRes(37),
	id-E-RABReleaseItem(38),
	id-E-RABSetupItemBearerSURes(39),
	id-SecurityContext(40),
	id-HandoverRestrictionList(41),
	id-UEPagingID(43),
	id-pagingDRX(44),
	id-TAIList(46),
	id-TAIItem(47),
	id-E-RABFailedToSetupListCtxtSURes(48),
	id-E-RABReleaseItemHOCmd(49),
	id-E-RABSetupItemCtxtSURes(50),
	id-E-RABSetupListCtxtSURes(51),
	id-E-RABToBeSetupItemCtxtSUReq(52),
	id-E-RABToBeSetupListHOReq(53),
	id-GERANtoLTEHOInformationRes(55),
	id-UTRANtoLTEHOInformationRes(57),
	id-CriticalityDiagnostics(58),
	id-Global-ENB-ID(59),
	id-eNBname(60),
	id-MMEname(61),
	id-ServedPLMNs(63),
	id-SupportedTAs(64),
	id-TimeToWait(65),
	id-uEaggregateMaximumBitrate(66),
	id-TAI(67),
	id-E-RABReleaseListBearerRelComp(69),
	id-cdma2000PDU(70),
	id-cdma2000RATType(71),
	id-cdma2000SectorID(72),
	id-SecurityKey(73),
	id-UERadioCapability(74),
	id-GUMMEI-ID(75),
	id-E-RABInformationListItem(78),
	id-Direct-Forwarding-Path-Availability(79),
	id-UEIdentityIndexValue(80),
	id-cdma2000HOStatus(83),
	id-cdma2000HORequiredIndication(84),
	id-E-UTRAN-Trace-ID(86),
	id-RelativeMMECapacity(87),
	id-SourceMME-UE-S1AP-ID(88),
	id-Bearers-SubjectToStatusTransfer-Item(89),
	id-eNB-StatusTransfer-TransparentContainer(90),
	id-UE-associatedLogicalS1-ConnectionItem(91),
	id-ResetType(92),
	id-UE-associatedLogicalS1-ConnectionListResAck(93),
	id-E-RABToBeSwitchedULItem(94),
	id-E-RABToBeSwitchedULList(95),
	id-S-TMSI(96),
	id-cdma2000OneXRAND(97),
	id-RequestType(98),
	id-UE-S1AP-IDs(99),
	id-EUTRAN-CGI(100),
	id-OverloadResponse(101),
	id-cdma2000OneXSRVCCInfo(102),
	id-E-RABFailedToBeReleasedList(103),
	id-Source-ToTarget-TransparentContainer(104),
	id-ServedGUMMEIs(105),
	id-SubscriberProfileIDforRFP(106),
	id-UESecurityCapabilities(107),
	id-CSFallbackIndicator(108),
	id-CNDomain(109),
	id-E-RABReleasedList(110),
	id-MessageIdentifier(111),
	id-SerialNumber(112),
	id-WarningAreaList(113),
	id-RepetitionPeriod(114),
	id-NumberofBroadcastRequest(115),
	id-WarningType(116),
	id-WarningSecurityInfo(117),
	id-DataCodingScheme(118),
	id-WarningMessageContents(119),
	id-BroadcastCompletedAreaList(120),
	id-Inter-SystemInformationTransferTypeEDT(121),
	id-Inter-SystemInformationTransferTypeMDT(122),
	id-Target-ToSource-TransparentContainer(123),
	id-SRVCCOperationPossible(124),
	id-SRVCCHOIndication(125),
	id-NAS-DownlinkCount(126),
	id-CSG-Id(127),
	id-CSG-IdList(128),
	id-SONConfigurationTransferECT(129),
	id-SONConfigurationTransferMCT(130),
	id-TraceCollectionEntityIPAddress(131),
	id-MSClassmark2(132),
	id-MSClassmark3(133),
	id-RRC-Establishment-Cause(134),
	id-NASSecurityParametersfromE-UTRAN(135),
	id-NASSecurityParameterstoE-UTRAN(136),
	id-DefaultPagingDRX(137),
	id-Source-ToTarget-TransparentContainer-Secondary(138),
	id-Target-ToSource-TransparentContainer-Secondary(139),
	id-EUTRANRoundTripDelayEstimationInfo(140),
	id-BroadcastCancelledAreaList(141),
	id-ConcurrentWarningMessageIndicator(142),
	id-Data-Forwarding-Not-Possible(143),
	id-ExtendedRepetitionPeriod(144),
	id-CellAccessMode(145),
	id-CSGMembershipStatus(146),
	id-LPPa-PDU(147),
	id-Routing-ID(148),
	id-Time-Synchronisation-Info(149),
	id-PS-ServiceNotAvailable(150),
	id-PagingPriority(151),
	id-x2TNLConfigurationInfo(152),
	id-eNBX2ExtendedTransportLayerAddresses(153),
	id-GUMMEIList(154),
	id-GW-TransportLayerAddress(155),
	id-Correlation-ID(156),
	id-SourceMME-GUMMEI(157),
	id-MME-UE-S1AP-ID-2(158),
	id-RegisteredLAI(159),
	id-RelayNode-Indicator(160),
	id-TrafficLoadReductionIndication(161),
	id-MDTConfiguration(162),
	id-MMERelaySupportIndicator(163),
	id-GWContextReleaseIndication(164),
	id-ManagementBasedMDTAllowed(165),
	id-PrivacyIndicator(166),
	id-Time-UE-StayedInCell-EnhancedGranularity(167),
	id-HO-Cause(168),
	id-VoiceSupportMatchIndicator(169),
	id-GUMMEIType(170),
	id-M3Configuration(171),
	id-M4Configuration(172),
	id-M5Configuration(173),
	id-MDT-Location-Info(174),
	id-MobilityInformation(175),
	id-Tunnel-Information-for-BBF(176),
	id-ManagementBasedMDTPLMNList(177),
	id-SignallingBasedMDTPLMNList(178),
	id-ULCOUNTValueExtended(179),
	id-DLCOUNTValueExtended(180),
	id-ReceiveStatusOfULPDCPSDUsExtended(181),
	id-ECGIListForRestart(182),
	id-SIPTO-Correlation-ID(183),
	id-SIPTO-L-GW-TransportLayerAddress(184),
	id-TransportInformation(185),
	id-LHN-ID(186),
	id-AdditionalCSFallbackIndicator(187),
	id-TAIListForRestart(188),
	id-UserLocationInformation(189),
	id-EmergencyAreaIDListForRestart(190),
	id-KillAllWarningMessages(191),
	id-Masked-IMEISV(192),
	id-eNBIndirectX2TransportLayerAddresses(193),
	id-uE-HistoryInformationFromTheUE(194),
	id-ProSeAuthorized(195),
	id-ExpectedUEBehaviour(196),
	id-LoggedMBSFNMDT(197),
	id-UERadioCapabilityForPaging(198),
	id-E-RABToBeModifiedListBearerModInd(199),
	id-E-RABToBeModifiedItemBearerModInd(200),
	id-E-RABNotToBeModifiedListBearerModInd(201),
	id-E-RABNotToBeModifiedItemBearerModInd(202),
	id-E-RABModifyListBearerModConf(203),
	id-E-RABModifyItemBearerModConf(204),
	id-E-RABFailedToModifyListBearerModConf(205),
	id-SON-Information-Report(206),
	id-Muting-Availability-Indication(207),
	id-Muting-Pattern-Information(208),
	id-Synchronisation-Information(209),
	id-E-RABToBeReleasedListBearerModConf(210),
	id-AssistanceDataForPaging(211),
	id-CellIdentifierAndCELevelForCECapableUEs(212),
	id-InformationOnRecommendedCellsAndENBsForPaging(213),
	id-RecommendedCellItem(214),
	id-RecommendedENBItem(215),
	id-ProSeUEtoNetworkRelaying(216),
	id-ULCOUNTValuePDCP-SNlength18(217),
	id-DLCOUNTValuePDCP-SNlength18(218),
	id-ReceiveStatusOfULPDCPSDUsPDCP-SNlength18(219),
	id-M6Configuration(220),
	id-M7Configuration(221),
	id-PWSfailedECGIList(222),
	id-MME-Group-ID(223),
	id-Additional-GUTI(224),
	id-S1-Message(225),
	id-CSGMembershipInfo(226),
	id-Paging-eDRXInformation(227),
	id-UE-RetentionInformation(228),
	id-UE-Usage-Type(230),
	id-extended-UEIdentityIndexValue(231),
	id-RAT-Type(232),
	id-BearerType(233),
	id-NB-IoT-DefaultPagingDRX(234),
	id-E-RABFailedToResumeListResumeReq(235),
	id-E-RABFailedToResumeItemResumeReq(236),
	id-E-RABFailedToResumeListResumeRes(237),
	id-E-RABFailedToResumeItemResumeRes(238),
	id-NB-IoT-Paging-eDRXInformation(239),
	id-V2XServicesAuthorized(240),
	id-UEUserPlaneCIoTSupportIndicator(241),
	id-CE-mode-B-SupportIndicator(242),
	id-SRVCCOperationNotPossible(243),
	id-NB-IoT-UEIdentityIndexValue(244),
	id-RRC-Resume-Cause(245),
	id-DCN-ID(246),
	id-ServedDCNs(247),
	id-UESidelinkAggregateMaximumBitrate(248),
	id-DLNASPDUDeliveryAckRequest(249),
	id-Coverage-Level(250),
	id-EnhancedCoverageRestricted(251),
	id-UE-Level-QoS-Parameters(252),
	id-DL-CP-SecurityInformation(253),
	id-UL-CP-SecurityInformation(254),
	id-extended-e-RAB-MaximumBitrateDL(255),
	id-extended-e-RAB-MaximumBitrateUL(256),
	id-extended-e-RAB-GuaranteedBitrateDL(257),
	id-extended-e-RAB-GuaranteedBitrateUL(258),
	id-extended-uEaggregateMaximumBitRateDL(259),
	id-extended-uEaggregateMaximumBitRateUL(260),
	id-NRrestrictioninEPSasSecondaryRAT(261),
	id-UEAppLayerMeasConfig(262),
	id-UE-Application-Layer-Measurement-Capability(263),
	id-SecondaryRATDataUsageReportList(264),
	id-SecondaryRATDataUsageReportItem(265),
	id-HandoverFlag(266),
	id-E-RABUsageReportItem(267),
	id-SecondaryRATDataUsageRequest(268),
	id-NRUESecurityCapabilities(269),
	id-UnlicensedSpectrumRestriction(270),
	id-CE-ModeBRestricted(271),
	id-LTE-M-Indication(272),
	id-DownlinkPacketLossRate(273),
	id-UplinkPacketLossRate(274),
	id-UECapabilityInfoRequest(275),
	id-serviceType(276),
	id-AerialUEsubscriptionInformation(277),
	id-Subscription-Based-UE-DifferentiationInfo(278),
	id-EndIndication(280),
	id-EDT-Session(281),
	id-CNTypeRestrictions(282),
	id-PendingDataIndication(283),
	id-BluetoothMeasurementConfiguration(284),
	id-WLANMeasurementConfiguration(285),
	id-WarningAreaCoordinates(286),
	id-NRrestrictionin5GS(287),
	id-PSCellInformation(288),
	id-LastNG-RANPLMNIdentity(290),
	id-ConnectedengNBList(291),
	id-ConnectedengNBToAddList(292),
	id-ConnectedengNBToRemoveList(293),
	id-EN-DCSONConfigurationTransfer-ECT(294),
	id-EN-DCSONConfigurationTransfer-MCT(295),
	id-IMSvoiceEPSfallbackfrom5G(296),
	id-TimeSinceSecondaryNodeRelease(297),
	id-RequestTypeAdditionalInfo(298),
	id-AdditionalRRMPriorityIndex(299),
	id-ContextatSource(300)
} (0..65535)

S1ap-TriggeringMessage ::= ENUMERATED { initiating-message, successful-outcome, unsuccessfull-outcome }

END
