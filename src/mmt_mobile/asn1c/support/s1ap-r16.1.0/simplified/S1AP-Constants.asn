-- Derived from 36413-g10.asn by src/mmt_mobile/asn1c/s1ap-simplify.py (issue #523).
-- Do not edit: `make -C src/mmt_mobile/asn1c gen-s1ap` rewrites it.

S1AP-Constants { itu-t (0) identified-organization (4) etsi (0) mobileDomain (0) eps-Access (21) modules (3) s1ap (1) version1 (1) s1ap-Constants (4) }

DEFINITIONS AUTOMATIC TAGS ::=

BEGIN

IMPORTS
	S1ap-ProcedureCode,
	S1ap-ProtocolIE-ID
FROM S1AP-CommonDataTypes;

s1ap-id-HandoverPreparation S1ap-ProcedureCode ::= 0

s1ap-id-HandoverResourceAllocation S1ap-ProcedureCode ::= 1

s1ap-id-HandoverNotification S1ap-ProcedureCode ::= 2

s1ap-id-PathSwitchRequest S1ap-ProcedureCode ::= 3

s1ap-id-HandoverCancel S1ap-ProcedureCode ::= 4

s1ap-id-E-RABSetup S1ap-ProcedureCode ::= 5

s1ap-id-E-RABModify S1ap-ProcedureCode ::= 6

s1ap-id-E-RABRelease S1ap-ProcedureCode ::= 7

s1ap-id-E-RABReleaseIndication S1ap-ProcedureCode ::= 8

s1ap-id-InitialContextSetup S1ap-ProcedureCode ::= 9

s1ap-id-Paging S1ap-ProcedureCode ::= 10

s1ap-id-downlinkNASTransport S1ap-ProcedureCode ::= 11

s1ap-id-initialUEMessage S1ap-ProcedureCode ::= 12

s1ap-id-uplinkNASTransport S1ap-ProcedureCode ::= 13

s1ap-id-Reset S1ap-ProcedureCode ::= 14

s1ap-id-ErrorIndication S1ap-ProcedureCode ::= 15

s1ap-id-NASNonDeliveryIndication S1ap-ProcedureCode ::= 16

s1ap-id-S1Setup S1ap-ProcedureCode ::= 17

s1ap-id-UEContextReleaseRequest S1ap-ProcedureCode ::= 18

s1ap-id-DownlinkS1cdma2000tunnelling S1ap-ProcedureCode ::= 19

s1ap-id-UplinkS1cdma2000tunnelling S1ap-ProcedureCode ::= 20

s1ap-id-UEContextModification S1ap-ProcedureCode ::= 21

s1ap-id-UECapabilityInfoIndication S1ap-ProcedureCode ::= 22

s1ap-id-UEContextRelease S1ap-ProcedureCode ::= 23

s1ap-id-eNBStatusTransfer S1ap-ProcedureCode ::= 24

s1ap-id-MMEStatusTransfer S1ap-ProcedureCode ::= 25

s1ap-id-DeactivateTrace S1ap-ProcedureCode ::= 26

s1ap-id-TraceStart S1ap-ProcedureCode ::= 27

s1ap-id-TraceFailureIndication S1ap-ProcedureCode ::= 28

s1ap-id-ENBConfigurationUpdate S1ap-ProcedureCode ::= 29

s1ap-id-MMEConfigurationUpdate S1ap-ProcedureCode ::= 30

s1ap-id-LocationReportingControl S1ap-ProcedureCode ::= 31

s1ap-id-LocationReportingFailureIndication S1ap-ProcedureCode ::= 32

s1ap-id-LocationReport S1ap-ProcedureCode ::= 33

s1ap-id-OverloadStart S1ap-ProcedureCode ::= 34

s1ap-id-OverloadStop S1ap-ProcedureCode ::= 35

s1ap-id-WriteReplaceWarning S1ap-ProcedureCode ::= 36

s1ap-id-eNBDirectInformationTransfer S1ap-ProcedureCode ::= 37

s1ap-id-MMEDirectInformationTransfer S1ap-ProcedureCode ::= 38

s1ap-id-PrivateMessage S1ap-ProcedureCode ::= 39

s1ap-id-eNBConfigurationTransfer S1ap-ProcedureCode ::= 40

s1ap-id-MMEConfigurationTransfer S1ap-ProcedureCode ::= 41

s1ap-id-CellTrafficTrace S1ap-ProcedureCode ::= 42

s1ap-id-Kill S1ap-ProcedureCode ::= 43

s1ap-id-downlinkUEAssociatedLPPaTransport S1ap-ProcedureCode ::= 44

s1ap-id-uplinkUEAssociatedLPPaTransport S1ap-ProcedureCode ::= 45

s1ap-id-downlinkNonUEAssociatedLPPaTransport S1ap-ProcedureCode ::= 46

s1ap-id-uplinkNonUEAssociatedLPPaTransport S1ap-ProcedureCode ::= 47

s1ap-id-UERadioCapabilityMatch S1ap-ProcedureCode ::= 48

s1ap-id-PWSRestartIndication S1ap-ProcedureCode ::= 49

s1ap-id-E-RABModificationIndication S1ap-ProcedureCode ::= 50

s1ap-id-PWSFailureIndication S1ap-ProcedureCode ::= 51

s1ap-id-RerouteNASRequest S1ap-ProcedureCode ::= 52

s1ap-id-UEContextModificationIndication S1ap-ProcedureCode ::= 53

s1ap-id-ConnectionEstablishmentIndication S1ap-ProcedureCode ::= 54

s1ap-id-UEContextSuspend S1ap-ProcedureCode ::= 55

s1ap-id-UEContextResume S1ap-ProcedureCode ::= 56

s1ap-id-NASDeliveryIndication S1ap-ProcedureCode ::= 57

s1ap-id-RetrieveUEInformation S1ap-ProcedureCode ::= 58

s1ap-id-UEInformationTransfer S1ap-ProcedureCode ::= 59

s1ap-id-eNBCPRelocationIndication S1ap-ProcedureCode ::= 60

s1ap-id-MMECPRelocationIndication S1ap-ProcedureCode ::= 61

s1ap-id-SecondaryRATDataUsageReport S1ap-ProcedureCode ::= 62

s1ap-maxPrivateIEs INTEGER ::= 65535

s1ap-maxProtocolExtensions INTEGER ::= 65535

s1ap-maxProtocolIEs INTEGER ::= 65535

s1ap-maxnoofCSGs INTEGER ::= 256

s1ap-maxnoofE-RABs INTEGER ::= 256

s1ap-maxnoofTAIs INTEGER ::= 256

s1ap-maxnoofTACs INTEGER ::= 256

s1ap-maxnoofErrors INTEGER ::= 256

s1ap-maxnoofBPLMNs INTEGER ::= 6

s1ap-maxnoofPLMNsPerMME INTEGER ::= 32

s1ap-maxnoofEPLMNs INTEGER ::= 15

s1ap-maxnoofEPLMNsPlusOne INTEGER ::= 16

s1ap-maxnoofForbLACs INTEGER ::= 4096

s1ap-maxnoofForbTACs INTEGER ::= 4096

s1ap-maxnoofIndividualS1ConnectionsToReset INTEGER ::= 256

s1ap-maxnoofCellsinUEHistoryInfo INTEGER ::= 16

s1ap-maxnoofCellsineNB INTEGER ::= 256

s1ap-maxnoofTAIforWarning INTEGER ::= 65535

s1ap-maxnoofCellID INTEGER ::= 65535

s1ap-maxnoofDCNs INTEGER ::= 32

s1ap-maxnoofEmergencyAreaID INTEGER ::= 65535

s1ap-maxnoofCellinTAI INTEGER ::= 65535

s1ap-maxnoofCellinEAI INTEGER ::= 65535

s1ap-maxnoofeNBX2TLAs INTEGER ::= 2

s1ap-maxnoofeNBX2ExtTLAs INTEGER ::= 16

s1ap-maxnoofeNBX2GTPTLAs INTEGER ::= 16

s1ap-maxnoofRATs INTEGER ::= 8

s1ap-maxnoofGroupIDs INTEGER ::= 65535

s1ap-maxnoofMMECs INTEGER ::= 256

s1ap-maxnoofCellIDforMDT INTEGER ::= 32

s1ap-maxnoofTAforMDT INTEGER ::= 8

s1ap-maxnoofMDTPLMNs INTEGER ::= 16

s1ap-maxnoofCellsforRestart INTEGER ::= 256

s1ap-maxnoofRestartTAIs INTEGER ::= 2048

s1ap-maxnoofRestartEmergencyAreaIDs INTEGER ::= 256

s1ap-maxEARFCN INTEGER ::= 262143

s1ap-maxnoofMBSFNAreaMDT INTEGER ::= 8

s1ap-maxnoofRecommendedCells INTEGER ::= 16

s1ap-maxnoofRecommendedENBs INTEGER ::= 16

s1ap-maxnooftimeperiods INTEGER ::= 2

s1ap-maxnoofCellIDforQMC INTEGER ::= 32

s1ap-maxnoofTAforQMC INTEGER ::= 8

s1ap-maxnoofPLMNforQMC INTEGER ::= 16

s1ap-maxnoofBluetoothName INTEGER ::= 4

s1ap-maxnoofWLANName INTEGER ::= 4

s1ap-maxnoofConnectedengNBs INTEGER ::= 256

s1ap-id-MME-UE-S1AP-ID S1ap-ProtocolIE-ID ::= 0

s1ap-id-HandoverType S1ap-ProtocolIE-ID ::= 1

s1ap-id-Cause S1ap-ProtocolIE-ID ::= 2

s1ap-id-SourceID S1ap-ProtocolIE-ID ::= 3

s1ap-id-TargetID S1ap-ProtocolIE-ID ::= 4

s1ap-id-eNB-UE-S1AP-ID S1ap-ProtocolIE-ID ::= 8

s1ap-id-E-RABSubjecttoDataForwardingList S1ap-ProtocolIE-ID ::= 12

s1ap-id-E-RABtoReleaseListHOCmd S1ap-ProtocolIE-ID ::= 13

s1ap-id-E-RABDataForwardingItem S1ap-ProtocolIE-ID ::= 14

s1ap-id-E-RABReleaseItemBearerRelComp S1ap-ProtocolIE-ID ::= 15

s1ap-id-E-RABToBeSetupListBearerSUReq S1ap-ProtocolIE-ID ::= 16

s1ap-id-E-RABToBeSetupItemBearerSUReq S1ap-ProtocolIE-ID ::= 17

s1ap-id-E-RABAdmittedList S1ap-ProtocolIE-ID ::= 18

s1ap-id-E-RABFailedToSetupListHOReqAck S1ap-ProtocolIE-ID ::= 19

s1ap-id-E-RABAdmittedItem S1ap-ProtocolIE-ID ::= 20

s1ap-id-E-RABFailedtoSetupItemHOReqAck S1ap-ProtocolIE-ID ::= 21

s1ap-id-E-RABToBeSwitchedDLList S1ap-ProtocolIE-ID ::= 22

s1ap-id-E-RABToBeSwitchedDLItem S1ap-ProtocolIE-ID ::= 23

s1ap-id-E-RABToBeSetupListCtxtSUReq S1ap-ProtocolIE-ID ::= 24

s1ap-id-TraceActivation S1ap-ProtocolIE-ID ::= 25

s1ap-id-NAS-PDU S1ap-ProtocolIE-ID ::= 26

s1ap-id-E-RABToBeSetupItemHOReq S1ap-ProtocolIE-ID ::= 27

s1ap-id-E-RABSetupListBearerSURes S1ap-ProtocolIE-ID ::= 28

s1ap-id-E-RABFailedToSetupListBearerSURes S1ap-ProtocolIE-ID ::= 29

s1ap-id-E-RABToBeModifiedListBearerModReq S1ap-ProtocolIE-ID ::= 30

s1ap-id-E-RABModifyListBearerModRes S1ap-ProtocolIE-ID ::= 31

s1ap-id-E-RABFailedToModifyList S1ap-ProtocolIE-ID ::= 32

s1ap-id-E-RABToBeReleasedList S1ap-ProtocolIE-ID ::= 33

s1ap-id-E-RABFailedToReleaseList S1ap-ProtocolIE-ID ::= 34

s1ap-id-E-RABItem S1ap-ProtocolIE-ID ::= 35

s1ap-id-E-RABToBeModifiedItemBearerModReq S1ap-ProtocolIE-ID ::= 36

s1ap-id-E-RABModifyItemBearerModRes S1ap-ProtocolIE-ID ::= 37

s1ap-id-E-RABReleaseItem S1ap-ProtocolIE-ID ::= 38

s1ap-id-E-RABSetupItemBearerSURes S1ap-ProtocolIE-ID ::= 39

s1ap-id-SecurityContext S1ap-ProtocolIE-ID ::= 40

s1ap-id-HandoverRestrictionList S1ap-ProtocolIE-ID ::= 41

s1ap-id-UEPagingID S1ap-ProtocolIE-ID ::= 43

s1ap-id-pagingDRX S1ap-ProtocolIE-ID ::= 44

s1ap-id-TAIList S1ap-ProtocolIE-ID ::= 46

s1ap-id-TAIItem S1ap-ProtocolIE-ID ::= 47

s1ap-id-E-RABFailedToSetupListCtxtSURes S1ap-ProtocolIE-ID ::= 48

s1ap-id-E-RABReleaseItemHOCmd S1ap-ProtocolIE-ID ::= 49

s1ap-id-E-RABSetupItemCtxtSURes S1ap-ProtocolIE-ID ::= 50

s1ap-id-E-RABSetupListCtxtSURes S1ap-ProtocolIE-ID ::= 51

s1ap-id-E-RABToBeSetupItemCtxtSUReq S1ap-ProtocolIE-ID ::= 52

s1ap-id-E-RABToBeSetupListHOReq S1ap-ProtocolIE-ID ::= 53

s1ap-id-GERANtoLTEHOInformationRes S1ap-ProtocolIE-ID ::= 55

s1ap-id-UTRANtoLTEHOInformationRes S1ap-ProtocolIE-ID ::= 57

s1ap-id-CriticalityDiagnostics S1ap-ProtocolIE-ID ::= 58

s1ap-id-Global-ENB-ID S1ap-ProtocolIE-ID ::= 59

s1ap-id-eNBname S1ap-ProtocolIE-ID ::= 60

s1ap-id-MMEname S1ap-ProtocolIE-ID ::= 61

s1ap-id-ServedPLMNs S1ap-ProtocolIE-ID ::= 63

s1ap-id-SupportedTAs S1ap-ProtocolIE-ID ::= 64

s1ap-id-TimeToWait S1ap-ProtocolIE-ID ::= 65

s1ap-id-uEaggregateMaximumBitrate S1ap-ProtocolIE-ID ::= 66

s1ap-id-TAI S1ap-ProtocolIE-ID ::= 67

s1ap-id-E-RABReleaseListBearerRelComp S1ap-ProtocolIE-ID ::= 69

s1ap-id-cdma2000PDU S1ap-ProtocolIE-ID ::= 70

s1ap-id-cdma2000RATType S1ap-ProtocolIE-ID ::= 71

s1ap-id-cdma2000SectorID S1ap-ProtocolIE-ID ::= 72

s1ap-id-SecurityKey S1ap-ProtocolIE-ID ::= 73

s1ap-id-UERadioCapability S1ap-ProtocolIE-ID ::= 74

s1ap-id-GUMMEI-ID S1ap-ProtocolIE-ID ::= 75

s1ap-id-E-RABInformationListItem S1ap-ProtocolIE-ID ::= 78

s1ap-id-Direct-Forwarding-Path-Availability S1ap-ProtocolIE-ID ::= 79

s1ap-id-UEIdentityIndexValue S1ap-ProtocolIE-ID ::= 80

s1ap-id-cdma2000HOStatus S1ap-ProtocolIE-ID ::= 83

s1ap-id-cdma2000HORequiredIndication S1ap-ProtocolIE-ID ::= 84

s1ap-id-E-UTRAN-Trace-ID S1ap-ProtocolIE-ID ::= 86

s1ap-id-RelativeMMECapacity S1ap-ProtocolIE-ID ::= 87

s1ap-id-SourceMME-UE-S1AP-ID S1ap-ProtocolIE-ID ::= 88

s1ap-id-Bearers-SubjectToStatusTransfer-Item S1ap-ProtocolIE-ID ::= 89

s1ap-id-eNB-StatusTransfer-TransparentContainer S1ap-ProtocolIE-ID ::= 90

s1ap-id-UE-associatedLogicalS1-ConnectionItem S1ap-ProtocolIE-ID ::= 91

s1ap-id-ResetType S1ap-ProtocolIE-ID ::= 92

s1ap-id-UE-associatedLogicalS1-ConnectionListResAck S1ap-ProtocolIE-ID ::= 93

s1ap-id-E-RABToBeSwitchedULItem S1ap-ProtocolIE-ID ::= 94

s1ap-id-E-RABToBeSwitchedULList S1ap-ProtocolIE-ID ::= 95

s1ap-id-S-TMSI S1ap-ProtocolIE-ID ::= 96

s1ap-id-cdma2000OneXRAND S1ap-ProtocolIE-ID ::= 97

s1ap-id-RequestType S1ap-ProtocolIE-ID ::= 98

s1ap-id-UE-S1AP-IDs S1ap-ProtocolIE-ID ::= 99

s1ap-id-EUTRAN-CGI S1ap-ProtocolIE-ID ::= 100

s1ap-id-OverloadResponse S1ap-ProtocolIE-ID ::= 101

s1ap-id-cdma2000OneXSRVCCInfo S1ap-ProtocolIE-ID ::= 102

s1ap-id-E-RABFailedToBeReleasedList S1ap-ProtocolIE-ID ::= 103

s1ap-id-Source-ToTarget-TransparentContainer S1ap-ProtocolIE-ID ::= 104

s1ap-id-ServedGUMMEIs S1ap-ProtocolIE-ID ::= 105

s1ap-id-SubscriberProfileIDforRFP S1ap-ProtocolIE-ID ::= 106

s1ap-id-UESecurityCapabilities S1ap-ProtocolIE-ID ::= 107

s1ap-id-CSFallbackIndicator S1ap-ProtocolIE-ID ::= 108

s1ap-id-CNDomain S1ap-ProtocolIE-ID ::= 109

s1ap-id-E-RABReleasedList S1ap-ProtocolIE-ID ::= 110

s1ap-id-MessageIdentifier S1ap-ProtocolIE-ID ::= 111

s1ap-id-SerialNumber S1ap-ProtocolIE-ID ::= 112

s1ap-id-WarningAreaList S1ap-ProtocolIE-ID ::= 113

s1ap-id-RepetitionPeriod S1ap-ProtocolIE-ID ::= 114

s1ap-id-NumberofBroadcastRequest S1ap-ProtocolIE-ID ::= 115

s1ap-id-WarningType S1ap-ProtocolIE-ID ::= 116

s1ap-id-WarningSecurityInfo S1ap-ProtocolIE-ID ::= 117

s1ap-id-DataCodingScheme S1ap-ProtocolIE-ID ::= 118

s1ap-id-WarningMessageContents S1ap-ProtocolIE-ID ::= 119

s1ap-id-BroadcastCompletedAreaList S1ap-ProtocolIE-ID ::= 120

s1ap-id-Inter-SystemInformationTransferTypeEDT S1ap-ProtocolIE-ID ::= 121

s1ap-id-Inter-SystemInformationTransferTypeMDT S1ap-ProtocolIE-ID ::= 122

s1ap-id-Target-ToSource-TransparentContainer S1ap-ProtocolIE-ID ::= 123

s1ap-id-SRVCCOperationPossible S1ap-ProtocolIE-ID ::= 124

s1ap-id-SRVCCHOIndication S1ap-ProtocolIE-ID ::= 125

s1ap-id-NAS-DownlinkCount S1ap-ProtocolIE-ID ::= 126

s1ap-id-CSG-Id S1ap-ProtocolIE-ID ::= 127

s1ap-id-CSG-IdList S1ap-ProtocolIE-ID ::= 128

s1ap-id-SONConfigurationTransferECT S1ap-ProtocolIE-ID ::= 129

s1ap-id-SONConfigurationTransferMCT S1ap-ProtocolIE-ID ::= 130

s1ap-id-TraceCollectionEntityIPAddress S1ap-ProtocolIE-ID ::= 131

s1ap-id-MSClassmark2 S1ap-ProtocolIE-ID ::= 132

s1ap-id-MSClassmark3 S1ap-ProtocolIE-ID ::= 133

s1ap-id-RRC-Establishment-Cause S1ap-ProtocolIE-ID ::= 134

s1ap-id-NASSecurityParametersfromE-UTRAN S1ap-ProtocolIE-ID ::= 135

s1ap-id-NASSecurityParameterstoE-UTRAN S1ap-ProtocolIE-ID ::= 136

s1ap-id-DefaultPagingDRX S1ap-ProtocolIE-ID ::= 137

s1ap-id-Source-ToTarget-TransparentContainer-Secondary S1ap-ProtocolIE-ID ::= 138

s1ap-id-Target-ToSource-TransparentContainer-Secondary S1ap-ProtocolIE-ID ::= 139

s1ap-id-EUTRANRoundTripDelayEstimationInfo S1ap-ProtocolIE-ID ::= 140

s1ap-id-BroadcastCancelledAreaList S1ap-ProtocolIE-ID ::= 141

s1ap-id-ConcurrentWarningMessageIndicator S1ap-ProtocolIE-ID ::= 142

s1ap-id-Data-Forwarding-Not-Possible S1ap-ProtocolIE-ID ::= 143

s1ap-id-ExtendedRepetitionPeriod S1ap-ProtocolIE-ID ::= 144

s1ap-id-CellAccessMode S1ap-ProtocolIE-ID ::= 145

s1ap-id-CSGMembershipStatus S1ap-ProtocolIE-ID ::= 146

s1ap-id-LPPa-PDU S1ap-ProtocolIE-ID ::= 147

s1ap-id-Routing-ID S1ap-ProtocolIE-ID ::= 148

s1ap-id-Time-Synchronisation-Info S1ap-ProtocolIE-ID ::= 149

s1ap-id-PS-ServiceNotAvailable S1ap-ProtocolIE-ID ::= 150

s1ap-id-PagingPriority S1ap-ProtocolIE-ID ::= 151

s1ap-id-x2TNLConfigurationInfo S1ap-ProtocolIE-ID ::= 152

s1ap-id-eNBX2ExtendedTransportLayerAddresses S1ap-ProtocolIE-ID ::= 153

s1ap-id-GUMMEIList S1ap-ProtocolIE-ID ::= 154

s1ap-id-GW-TransportLayerAddress S1ap-ProtocolIE-ID ::= 155

s1ap-id-Correlation-ID S1ap-ProtocolIE-ID ::= 156

s1ap-id-SourceMME-GUMMEI S1ap-ProtocolIE-ID ::= 157

s1ap-id-MME-UE-S1AP-ID-2 S1ap-ProtocolIE-ID ::= 158

s1ap-id-RegisteredLAI S1ap-ProtocolIE-ID ::= 159

s1ap-id-RelayNode-Indicator S1ap-ProtocolIE-ID ::= 160

s1ap-id-TrafficLoadReductionIndication S1ap-ProtocolIE-ID ::= 161

s1ap-id-MDTConfiguration S1ap-ProtocolIE-ID ::= 162

s1ap-id-MMERelaySupportIndicator S1ap-ProtocolIE-ID ::= 163

s1ap-id-GWContextReleaseIndication S1ap-ProtocolIE-ID ::= 164

s1ap-id-ManagementBasedMDTAllowed S1ap-ProtocolIE-ID ::= 165

s1ap-id-PrivacyIndicator S1ap-ProtocolIE-ID ::= 166

s1ap-id-Time-UE-StayedInCell-EnhancedGranularity S1ap-ProtocolIE-ID ::= 167

s1ap-id-HO-Cause S1ap-ProtocolIE-ID ::= 168

s1ap-id-VoiceSupportMatchIndicator S1ap-ProtocolIE-ID ::= 169

s1ap-id-GUMMEIType S1ap-ProtocolIE-ID ::= 170

s1ap-id-M3Configuration S1ap-ProtocolIE-ID ::= 171

s1ap-id-M4Configuration S1ap-ProtocolIE-ID ::= 172

s1ap-id-M5Configuration S1ap-ProtocolIE-ID ::= 173

s1ap-id-MDT-Location-Info S1ap-ProtocolIE-ID ::= 174

s1ap-id-MobilityInformation S1ap-ProtocolIE-ID ::= 175

s1ap-id-Tunnel-Information-for-BBF S1ap-ProtocolIE-ID ::= 176

s1ap-id-ManagementBasedMDTPLMNList S1ap-ProtocolIE-ID ::= 177

s1ap-id-SignallingBasedMDTPLMNList S1ap-ProtocolIE-ID ::= 178

s1ap-id-ULCOUNTValueExtended S1ap-ProtocolIE-ID ::= 179

s1ap-id-DLCOUNTValueExtended S1ap-ProtocolIE-ID ::= 180

s1ap-id-ReceiveStatusOfULPDCPSDUsExtended S1ap-ProtocolIE-ID ::= 181

s1ap-id-ECGIListForRestart S1ap-ProtocolIE-ID ::= 182

s1ap-id-SIPTO-Correlation-ID S1ap-ProtocolIE-ID ::= 183

s1ap-id-SIPTO-L-GW-TransportLayerAddress S1ap-ProtocolIE-ID ::= 184

s1ap-id-TransportInformation S1ap-ProtocolIE-ID ::= 185

s1ap-id-LHN-ID S1ap-ProtocolIE-ID ::= 186

s1ap-id-AdditionalCSFallbackIndicator S1ap-ProtocolIE-ID ::= 187

s1ap-id-TAIListForRestart S1ap-ProtocolIE-ID ::= 188

s1ap-id-UserLocationInformation S1ap-ProtocolIE-ID ::= 189

s1ap-id-EmergencyAreaIDListForRestart S1ap-ProtocolIE-ID ::= 190

s1ap-id-KillAllWarningMessages S1ap-ProtocolIE-ID ::= 191

s1ap-id-Masked-IMEISV S1ap-ProtocolIE-ID ::= 192

s1ap-id-eNBIndirectX2TransportLayerAddresses S1ap-ProtocolIE-ID ::= 193

s1ap-id-uE-HistoryInformationFromTheUE S1ap-ProtocolIE-ID ::= 194

s1ap-id-ProSeAuthorized S1ap-ProtocolIE-ID ::= 195

s1ap-id-ExpectedUEBehaviour S1ap-ProtocolIE-ID ::= 196

s1ap-id-LoggedMBSFNMDT S1ap-ProtocolIE-ID ::= 197

s1ap-id-UERadioCapabilityForPaging S1ap-ProtocolIE-ID ::= 198

s1ap-id-E-RABToBeModifiedListBearerModInd S1ap-ProtocolIE-ID ::= 199

s1ap-id-E-RABToBeModifiedItemBearerModInd S1ap-ProtocolIE-ID ::= 200

s1ap-id-E-RABNotToBeModifiedListBearerModInd S1ap-ProtocolIE-ID ::= 201

s1ap-id-E-RABNotToBeModifiedItemBearerModInd S1ap-ProtocolIE-ID ::= 202

s1ap-id-E-RABModifyListBearerModConf S1ap-ProtocolIE-ID ::= 203

s1ap-id-E-RABModifyItemBearerModConf S1ap-ProtocolIE-ID ::= 204

s1ap-id-E-RABFailedToModifyListBearerModConf S1ap-ProtocolIE-ID ::= 205

s1ap-id-SON-Information-Report S1ap-ProtocolIE-ID ::= 206

s1ap-id-Muting-Availability-Indication S1ap-ProtocolIE-ID ::= 207

s1ap-id-Muting-Pattern-Information S1ap-ProtocolIE-ID ::= 208

s1ap-id-Synchronisation-Information S1ap-ProtocolIE-ID ::= 209

s1ap-id-E-RABToBeReleasedListBearerModConf S1ap-ProtocolIE-ID ::= 210

s1ap-id-AssistanceDataForPaging S1ap-ProtocolIE-ID ::= 211

s1ap-id-CellIdentifierAndCELevelForCECapableUEs S1ap-ProtocolIE-ID ::= 212

s1ap-id-InformationOnRecommendedCellsAndENBsForPaging S1ap-ProtocolIE-ID ::= 213

s1ap-id-RecommendedCellItem S1ap-ProtocolIE-ID ::= 214

s1ap-id-RecommendedENBItem S1ap-ProtocolIE-ID ::= 215

s1ap-id-ProSeUEtoNetworkRelaying S1ap-ProtocolIE-ID ::= 216

s1ap-id-ULCOUNTValuePDCP-SNlength18 S1ap-ProtocolIE-ID ::= 217

s1ap-id-DLCOUNTValuePDCP-SNlength18 S1ap-ProtocolIE-ID ::= 218

s1ap-id-ReceiveStatusOfULPDCPSDUsPDCP-SNlength18 S1ap-ProtocolIE-ID ::= 219

s1ap-id-M6Configuration S1ap-ProtocolIE-ID ::= 220

s1ap-id-M7Configuration S1ap-ProtocolIE-ID ::= 221

s1ap-id-PWSfailedECGIList S1ap-ProtocolIE-ID ::= 222

s1ap-id-MME-Group-ID S1ap-ProtocolIE-ID ::= 223

s1ap-id-Additional-GUTI S1ap-ProtocolIE-ID ::= 224

s1ap-id-S1-Message S1ap-ProtocolIE-ID ::= 225

s1ap-id-CSGMembershipInfo S1ap-ProtocolIE-ID ::= 226

s1ap-id-Paging-eDRXInformation S1ap-ProtocolIE-ID ::= 227

s1ap-id-UE-RetentionInformation S1ap-ProtocolIE-ID ::= 228

s1ap-id-UE-Usage-Type S1ap-ProtocolIE-ID ::= 230

s1ap-id-extended-UEIdentityIndexValue S1ap-ProtocolIE-ID ::= 231

s1ap-id-RAT-Type S1ap-ProtocolIE-ID ::= 232

s1ap-id-BearerType S1ap-ProtocolIE-ID ::= 233

s1ap-id-NB-IoT-DefaultPagingDRX S1ap-ProtocolIE-ID ::= 234

s1ap-id-E-RABFailedToResumeListResumeReq S1ap-ProtocolIE-ID ::= 235

s1ap-id-E-RABFailedToResumeItemResumeReq S1ap-ProtocolIE-ID ::= 236

s1ap-id-E-RABFailedToResumeListResumeRes S1ap-ProtocolIE-ID ::= 237

s1ap-id-E-RABFailedToResumeItemResumeRes S1ap-ProtocolIE-ID ::= 238

s1ap-id-NB-IoT-Paging-eDRXInformation S1ap-ProtocolIE-ID ::= 239

s1ap-id-V2XServicesAuthorized S1ap-ProtocolIE-ID ::= 240

s1ap-id-UEUserPlaneCIoTSupportIndicator S1ap-ProtocolIE-ID ::= 241

s1ap-id-CE-mode-B-SupportIndicator S1ap-ProtocolIE-ID ::= 242

s1ap-id-SRVCCOperationNotPossible S1ap-ProtocolIE-ID ::= 243

s1ap-id-NB-IoT-UEIdentityIndexValue S1ap-ProtocolIE-ID ::= 244

s1ap-id-RRC-Resume-Cause S1ap-ProtocolIE-ID ::= 245

s1ap-id-DCN-ID S1ap-ProtocolIE-ID ::= 246

s1ap-id-ServedDCNs S1ap-ProtocolIE-ID ::= 247

s1ap-id-UESidelinkAggregateMaximumBitrate S1ap-ProtocolIE-ID ::= 248

s1ap-id-DLNASPDUDeliveryAckRequest S1ap-ProtocolIE-ID ::= 249

s1ap-id-Coverage-Level S1ap-ProtocolIE-ID ::= 250

s1ap-id-EnhancedCoverageRestricted S1ap-ProtocolIE-ID ::= 251

s1ap-id-UE-Level-QoS-Parameters S1ap-ProtocolIE-ID ::= 252

s1ap-id-DL-CP-SecurityInformation S1ap-ProtocolIE-ID ::= 253

s1ap-id-UL-CP-SecurityInformation S1ap-ProtocolIE-ID ::= 254

s1ap-id-extended-e-RAB-MaximumBitrateDL S1ap-ProtocolIE-ID ::= 255

s1ap-id-extended-e-RAB-MaximumBitrateUL S1ap-ProtocolIE-ID ::= 256

s1ap-id-extended-e-RAB-GuaranteedBitrateDL S1ap-ProtocolIE-ID ::= 257

s1ap-id-extended-e-RAB-GuaranteedBitrateUL S1ap-ProtocolIE-ID ::= 258

s1ap-id-extended-uEaggregateMaximumBitRateDL S1ap-ProtocolIE-ID ::= 259

s1ap-id-extended-uEaggregateMaximumBitRateUL S1ap-ProtocolIE-ID ::= 260

s1ap-id-NRrestrictioninEPSasSecondaryRAT S1ap-ProtocolIE-ID ::= 261

s1ap-id-UEAppLayerMeasConfig S1ap-ProtocolIE-ID ::= 262

s1ap-id-UE-Application-Layer-Measurement-Capability S1ap-ProtocolIE-ID ::= 263

s1ap-id-SecondaryRATDataUsageReportList S1ap-ProtocolIE-ID ::= 264

s1ap-id-SecondaryRATDataUsageReportItem S1ap-ProtocolIE-ID ::= 265

s1ap-id-HandoverFlag S1ap-ProtocolIE-ID ::= 266

s1ap-id-E-RABUsageReportItem S1ap-ProtocolIE-ID ::= 267

s1ap-id-SecondaryRATDataUsageRequest S1ap-ProtocolIE-ID ::= 268

s1ap-id-NRUESecurityCapabilities S1ap-ProtocolIE-ID ::= 269

s1ap-id-UnlicensedSpectrumRestriction S1ap-ProtocolIE-ID ::= 270

s1ap-id-CE-ModeBRestricted S1ap-ProtocolIE-ID ::= 271

s1ap-id-LTE-M-Indication S1ap-ProtocolIE-ID ::= 272

s1ap-id-DownlinkPacketLossRate S1ap-ProtocolIE-ID ::= 273

s1ap-id-UplinkPacketLossRate S1ap-ProtocolIE-ID ::= 274

s1ap-id-UECapabilityInfoRequest S1ap-ProtocolIE-ID ::= 275

s1ap-id-serviceType S1ap-ProtocolIE-ID ::= 276

s1ap-id-AerialUEsubscriptionInformation S1ap-ProtocolIE-ID ::= 277

s1ap-id-Subscription-Based-UE-DifferentiationInfo S1ap-ProtocolIE-ID ::= 278

s1ap-id-EndIndication S1ap-ProtocolIE-ID ::= 280

s1ap-id-EDT-Session S1ap-ProtocolIE-ID ::= 281

s1ap-id-CNTypeRestrictions S1ap-ProtocolIE-ID ::= 282

s1ap-id-PendingDataIndication S1ap-ProtocolIE-ID ::= 283

s1ap-id-BluetoothMeasurementConfiguration S1ap-ProtocolIE-ID ::= 284

s1ap-id-WLANMeasurementConfiguration S1ap-ProtocolIE-ID ::= 285

s1ap-id-WarningAreaCoordinates S1ap-ProtocolIE-ID ::= 286

s1ap-id-NRrestrictionin5GS S1ap-ProtocolIE-ID ::= 287

s1ap-id-PSCellInformation S1ap-ProtocolIE-ID ::= 288

s1ap-id-LastNG-RANPLMNIdentity S1ap-ProtocolIE-ID ::= 290

s1ap-id-ConnectedengNBList S1ap-ProtocolIE-ID ::= 291

s1ap-id-ConnectedengNBToAddList S1ap-ProtocolIE-ID ::= 292

s1ap-id-ConnectedengNBToRemoveList S1ap-ProtocolIE-ID ::= 293

s1ap-id-EN-DCSONConfigurationTransfer-ECT S1ap-ProtocolIE-ID ::= 294

s1ap-id-EN-DCSONConfigurationTransfer-MCT S1ap-ProtocolIE-ID ::= 295

s1ap-id-IMSvoiceEPSfallbackfrom5G S1ap-ProtocolIE-ID ::= 296

s1ap-id-TimeSinceSecondaryNodeRelease S1ap-ProtocolIE-ID ::= 297

s1ap-id-RequestTypeAdditionalInfo S1ap-ProtocolIE-ID ::= 298

s1ap-id-AdditionalRRMPriorityIndex S1ap-ProtocolIE-ID ::= 299

s1ap-id-ContextatSource S1ap-ProtocolIE-ID ::= 300

END
